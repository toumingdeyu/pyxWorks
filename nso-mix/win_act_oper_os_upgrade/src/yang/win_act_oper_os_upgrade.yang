module win_act_oper_os_upgrade {

  namespace "http://example.com/win_act_oper_os_upgrade";
  prefix win_act_oper_os_upgrade;

  import ietf-inet-types {
    prefix inet;
  }
  import tailf-common {
    prefix tailf;
  }
  import tailf-ncs {
    prefix ncs;
  }

  import win_common {
    prefix win;
  }
  import com_orange_common {
    prefix orange;
  }

  description
    "Bla bla...";

  revision 2016-01-01 {
    description
      "Initial revision.";
  }

  augment /orange:orange/orange:win {
    container win_act_oper_os_upgrade {
      tailf:info "";
      description "win_act_oper_os_upgrade package";
      container actions {
      }
    }
  }

  augment /orange:orange/orange:win/win_act_oper_os_upgrade:win_act_oper_os_upgrade/win_act_oper_os_upgrade:actions {
    tailf:action get_sw_version {
      tailf:actionpoint get_sw_version;
      input {
        leaf device {
          type leafref {
            path "/ncs:devices/ncs:device/ncs:name";
          }
        }
      }
      output {
        leaf os_type {
          type string;
        }
        leaf hw_type {
          type string;
        }
        leaf sw_version {
          type string;
        }
        leaf-list sw_patches {
          type string;
        }
        list target_sw_versions {
          leaf name {
            type string;
          }
          leaf path {
            type string;
          }
          leaf-list files {
            type string;
          }
          leaf-list patch_files {
            type string;
          }
          leaf patch_path {
            type string;
          }
        }
      }
    }


    tailf:action os_upgrade_install_add {
      tailf:actionpoint os_upgrade_install_add;
      input {
        leaf device {
          type leafref {
            path "/ncs:devices/ncs:device/ncs:name";
          }
        }
        leaf sw_version_selected_file {
            type string;
        }
        leaf patch_version_selected_files {
            type string;
        }
        leaf patch_version_selected_path {
            type string;
        }
      }
      output {
        leaf os_type {
          type string;
        }
        leaf hw_type {
          type string;
        }
        leaf operation_id {
          type string;
        }
        leaf install_log {
          type string;
        }
        leaf completed {
          type string;
        }
        leaf result {
          type string;
        }
      }
    }

    tailf:action os_upgrade_progress_check {
      tailf:actionpoint os_upgrade_progress_check;
      input {
        leaf device {
          type leafref {
            path "/ncs:devices/ncs:device/ncs:name";
          }
        }
        leaf operation_id {
          type string;
        }
        leaf operation_id_smu {
          type string;
        }
      }
      output {
        leaf os_type {
          type string;
        }
        leaf hw_type {
          type string;
        }
        leaf install_log {
          type string;
        }
        leaf operation_id {
          type string;
        }
        leaf last_command {
          type string;
        }
        leaf completed {
          type string;
        }
        leaf result {
          type string;
        }
      }
    }

    tailf:action os_upgrade_device_ping_check {
      tailf:actionpoint os_upgrade_device_ping_check;
      input {
        leaf device {
          type leafref {
            path "/ncs:devices/ncs:device/ncs:name";
          }
        }
        leaf ip {
          type string;
        }
      }
      output {
        leaf result {
          type string;
        }
      }
    }

    tailf:action os_upgrade_device_get_ip {
      tailf:actionpoint os_upgrade_device_get_ip;
      input {
        leaf device {
          type leafref {
            path "/ncs:devices/ncs:device/ncs:name";
          }
        }
      }
      output {
        leaf ip_address {
          type string;
        }
      }
    }

    tailf:action os_upgrade_install_prepare {
      tailf:actionpoint os_upgrade_install_prepare;
      input {
        leaf device {
          type leafref {
            path "/ncs:devices/ncs:device/ncs:name";
          }
        }
        leaf operation_id {
          type string;
        }
        leaf operation_id_smu {
          type string;
        }
      }
      output {
        leaf os_type {
          type string;
        }
        leaf hw_type {
          type string;
        }
        leaf operation_id {
          type string;
        }
        leaf install_log {
          type string;
        }
        leaf completed {
          type string;
        }
        leaf result {
          type string;
        }
      }
    }

    tailf:action os_upgrade_install_activate {
      tailf:actionpoint os_upgrade_install_activate;
      input {
        leaf device {
          type leafref {
            path "/ncs:devices/ncs:device/ncs:name";
          }
        }
        leaf operation_id {
          type string;
        }
        leaf operation_id_smu {
          type string;
        }
      }
      output {
        leaf os_type {
          type string;
        }
        leaf hw_type {
          type string;
        }
        leaf operation_id {
          type string;
        }
        leaf install_log {
          type string;
        }
        leaf last_command {
          type string;
        }
        leaf completed {
          type string;
        }
        leaf result {
          type string;
        }
      }
    }

    tailf:action os_upgrade_remove_inactive {
      tailf:actionpoint os_upgrade_remove_inactive;
      input {
        leaf device {
          type leafref {
            path "/ncs:devices/ncs:device/ncs:name";
          }
        }
      }
      output {
        leaf os_type {
          type string;
        }
        leaf hw_type {
          type string;
        }
        leaf operation_id {
          type string;
        }
        leaf last_command {
          type string;
        }
        leaf log {
          type string;
        }
      }
    }

    tailf:action os_upgrade_commit {
      tailf:actionpoint os_upgrade_commit;
      input {
        leaf device {
          type leafref {
            path "/ncs:devices/ncs:device/ncs:name";
          }
        }
      }
      output {
        leaf os_type {
          type string;
        }
        leaf hw_type {
          type string;
        }
        leaf operation_id {
          type string;
        }
        leaf last_command {
          type string;
        }
        leaf log {
          type string;
        }
      }
    }
  }

  list win_act_oper_os_upgrade {
    description "This is an RFS skeleton service";

    key name;
    leaf name {
      tailf:info "Unique service id";
      tailf:cli-allow-range;
      type string;
    }

    uses ncs:service-data;
    ncs:servicepoint win_act_oper_os_upgrade-servicepoint;

    // may replace this with other ways of refering to the devices.
    leaf-list device {
      type leafref {
        path "/ncs:devices/ncs:device/ncs:name";
      }
    }

    // replace with your own stuff here
    leaf dummy {
      type inet:ipv4-address;
    }
  }
}
